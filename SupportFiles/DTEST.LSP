(defun c:dtest ( / |fp |action |dcl @parse_path @yes_dcl |line |n |dialog |dialogs)
   (gc)
   ;;
   ;; Function to check if file has .DCL extension
   ;;
   (defun @yes_dcl (|dcl)
      (cond
         ((/= (type |dcl) 'STR) nil)
         ((< (strlen |dcl) 4) nil)
         ((= (strcase (substr |dcl (- (strlen |dcl) 3))) ".DCL") 1)
         (1 nil)
      )
   )
   ;;
   ;;  Find DCL name from full path name.
   ;;
   (defun @parse_path (|dcl / |name |a |b)
      (setq |a 1 |b nil)
      (repeat (strlen |dcl)
         (if (member (substr |dcl |a 1) '("/" "\\" ":"))
            (setq |b |a)
         )
         (setq |a (1+ |a))
      )
      (if |b
         (setq |name (strcase (substr |dcl (1+ |b))))
         (setq |name (strcase |dcl))
      )
      (if (@yes_dcl |name)
         (setq |name (substr |name 1 (- (strlen |name) 4)))
      )
      |name
   )
   (if (not $dialog)(setq $dialog ""))
   (if (setq ans (getfiled " Select File to View " $dialog "DCL" 2))
      (setq $dialog ans)
   )
   (if (/= $dialog "")
      (if (setq |fp (open $dialog "r"))
         (progn
            (while (setq |line (read-line |fp))
               (if (or (setq |n (vl-string-search ":DIALOG " (strcase |line)))
                       (setq |n (vl-string-search ":DIALOG" (strcase |line)))
                       (setq |n (vl-string-search ": DIALOG " (strcase |line)))
                       (setq |n (vl-string-search ": DIALOG" (strcase |line)))
                   )
                  (setq |dialog (@cv_ltrim (@cv_rtrim (substr |line 1 (1- |n))))
                        |dialogs (cons |dialog |dialogs)
                  )
               )
            )
            (setq |fp (close |fp)
                  |dialogs (reverse |dialogs)
            )
         )
      )
   )
   (if (and |dialogs (setq |dcl (load_dialog $dialog)))
      (progn
         (foreach |dialog |dialogs
            (princ (strcat "\nNew dialog: " |dialog "\n"))
            (setq |action 3)
            (if (new_dialog |dialog |dcl)
               (while (> |action 2)
                  (action_tile "accept" "(done_dialog 1)")
                  (action_tile "cancel" "(done_dialog 0)")
                  (setq |action (start_dialog))
               )
            )
         )
         (unload_dialog |dcl)
      )
   )
   (princ)
)
